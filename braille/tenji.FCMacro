# -*- coding: utf-8 -*-# 
# tenji.FCMacro (Japanese braille FreeCAD macro)
# version 0.1 by penkich 2020-09-15
#
FREECADPATH = "/usr/lib/freecad-python3/lib"
import sys
sys.path.append(FREECADPATH)
import numpy as np
import re
import FreeCAD as App
import Part
import FreeCADGui as Gui
import PySide # FreeCADに最初から入ってる


try:
    doc = App.getDocument('Unnamed')
except:
    App.newDocument()
    doc = App.getDocument('Unnamed')

ka = [6]     # か行
sa = [5,6]   # さ行
ta = [3,5]   # た行
na = [3]     # な行
ha = [3,6]   # は行
ma = [3,5,6] # ま行
ra = [5]     # ら行
dak = [5]    # 濁音
han = [6]    # 半濁音
nan = []     # 空
you = [4]    # 拗音符
dyo = [4,5]  # 濁音+拗音符
hyo = [4,6]  # 半濁音+拗音符
suji = [3,4,5,6] # 数符
gaiji = [5,6]    # 外字符
omoji = [6]   # 大文字符
tunagi = [3,6] # つなぎ符


# １文字系辞書
jdic = {'A':[[1]],        'B':[[1,2]],        'C':[[1,4]],      'D':[[1,4,5]],      'E':[[1,5]],
        'F':[[1,2,4]],    'G':[[1,2,4,5]],    'H':[[1,2,5]],    'I':[[2,4]],        'J':[[2,4,5]],
        'K':[[1]+[3]],    'L':[[1,2]+[3]],    'M':[[1,4]+[3]],  'N':[[1,4,5]+[3]],  'O':[[1,5]+[3]],
        'P':[[1,2,4]+[3]],'Q':[[1,2,4,5]+[3]],'R':[[1,2,5]+[3]],'S':[[2,4]+[3]],    'T':[[2,4,5]+[3]],
        'U':[[1]+[3,6]],  'V':[[1,2]+[3,6]],  'X':[[1,4]+[3,6]],'Y':[[1,4,5]+[3,6]],'Z':[[1,5]+[3,6]],
        'W':[[2,4,5,6]],
        'a':[[1]],        'b':[[1,2]],        'c':[[1,4]],      'd':[[1,4,5]],      'e':[[1,5]],
        'f':[[1,2,4]],    'g':[[1,2,4,5]],    'h':[[1,2,5]],    'i':[[2,4]],        'j':[[2,4,5]],
        'k':[[1]+[3]],    'l':[[1,2]+[3]],    'm':[[1,4]+[3]],  'n':[[1,4,5]+[3]],  'o':[[1,5]+[3]],
        'p':[[1,2,4]+[3]],'q':[[1,2,4,5]+[3]],'r':[[1,2,5]+[3]],'s':[[2,4]+[3]],    't':[[2,4,5]+[3]],
        'u':[[1]+[3,6]],  'v':[[1,2]+[3,6]],  'x':[[1,4]+[3,6]],'y':[[1,4,5]+[3,6]],'z':[[1,5]+[3,6]],
        'w':[[2,4,5,6]],
        '1':[[1]],        '2':[[1,2]],    '3':[[1,4]],    '4':[[1,4,5]],    '5':[[1,5]],
        '6':[[1,2,4]],    '7':[[1,2,4,5]],'8':[[1,2,5]],  '9':[[2,4]],      '0':[[2,4,5]],
        'あ':[     [1]],    'い':[     [1,2]],    'う':[     [1,4]],    'え':[     [1,2,4]],    'お':[     [2,4]],
        'か':[     [1]+ka], 'き':[     [1,2]+ka], 'く':[     [1,4]+ka], 'け':[     [1,2,4]+ka], 'こ':[     [2,4]+ka],
        'が':[dak, [1]+ka], 'ぎ':[dak, [1,2]+ka], 'ぐ':[dak, [1,4]+ka], 'げ':[dak, [1,2,4]+ka], 'ご':[dak, [2,4]+ka],
        'さ':[     [1]+sa], 'し':[     [1,2]+sa], 'す':[     [1,4]+sa], 'せ':[     [1,2,4]+sa], 'そ':[     [2,4]+sa],
        'ざ':[dak, [1]+sa], 'じ':[dak, [1,2]+sa], 'ず':[dak, [1,4]+sa], 'ぜ':[dak, [1,2,4]+sa], 'ぞ':[dak, [2,4]+sa],
        'た':[     [1]+ta], 'ち':[     [1,2]+ta], 'つ':[     [1,4]+ta], 'て':[     [1,2,4]+ta], 'と':[     [2,4]+ta],
        'だ':[dak, [1]+ta], 'ぢ':[dak, [1,2]+ta], 'づ':[dak, [1,4]+ta], 'で':[dak, [1,2,4]+ta], 'ど':[dak, [2,4]+ta],
        'な':[     [1]+na], 'に':[     [1,2]+na], 'ぬ':[     [1,4]+na], 'ね':[     [1,2,4]+na], 'の':[     [2,4]+na],
        'は':[     [1]+ha], 'ひ':[     [1,2]+ha], 'ふ':[     [1,4]+ha], 'へ':[     [1,2,4]+ha], 'ほ':[     [2,4]+ha],
        'ば':[dak, [1]+ha], 'び':[dak, [1,2]+ha], 'ぶ':[dak, [1,4]+ha], 'べ':[dak, [1,2,4]+ha], 'ぼ':[dak, [2,4]+ha],
        'ぱ':[han, [1]+ha], 'ぴ':[han, [1,2]+ha], 'ぷ':[han, [1,4]+ha], 'ぺ':[han, [1,2,4]+ha], 'ぽ':[han, [2,4]+ha],
        'ま':[     [1]+ma], 'み':[     [1,2]+ma], 'む':[     [1,4]+ma], 'め':[     [1,2,4]+ma], 'も':[     [2,4]+ma],
        'ら':[     [1]+ra], 'り':[     [1,2]+ra], 'る':[     [1,4]+ra], 'れ':[     [1,2,4]+ra], 'ろ':[     [2,4]+ra],
        'や':[     [3,4]],  'ゆ':[     [3,4,6]],  'よ':[     [3,4,5]],
        'わ':[     [3]],    'を':[     [3,5]],    'ん':[     [3,5,6]],  'っ':[[2]],
        '、':[[5,6], nan], '。':[[2,5,6], nan, nan], '？':[[2,6],nan,nan], '！':[[2,3,5],nan,nan], '・':[[5], nan], 'ー':[[2,5]],
        '．':[[2,5,6], nan],
        '　':[nan], # スペース（全角）
        ' ':[nan], # スペース（半角）
        'ゔ':[[5],[1,4]],
        '→':[nan, [2,5],[2,5],[1,3,5],nan],
        '←':[nan, [2,4,6],[2,5],[2,5],nan],
        '（':[[2,3,5,6]], '）':[[2,3,5,6]],
        '「':[[5,6],[3]], '」':[[6],[2,3]],
        '～':[[3,6],[3,6]],
        '－':[[2,5],[2,5]],
        '外':[gaiji], '数':[suji], '大':[omoji], '継':[tunagi],
        '拡':[omoji, omoji] # 二重大文字符
        }

# ２文字系辞書
jdic2 = { 'きゃ':[you, jdic['か'][0]], 'きゅ':[you, jdic['く'][0]], 'きょ':[you, jdic['こ'][0]],
          'しゃ':[you, jdic['さ'][0]], 'しゅ':[you, jdic['す'][0]], 'しょ':[you, jdic['そ'][0]],
          'ちゃ':[you, jdic['た'][0]], 'ちゅ':[you, jdic['つ'][0]], 'ちょ':[you, jdic['と'][0]],
          'にゃ':[you, jdic['な'][0]], 'にゅ':[you, jdic['ぬ'][0]], 'にょ':[you, jdic['の'][0]],
          'ひゃ':[you, jdic['は'][0]], 'ひゅ':[you, jdic['ふ'][0]], 'ひょ':[you, jdic['ほ'][0]],
          'みゃ':[you, jdic['ま'][0]], 'みゅ':[you, jdic['む'][0]], 'みょ':[you, jdic['も'][0]],
          'りゃ':[you, jdic['ら'][0]], 'りゅ':[you, jdic['る'][0]], 'りょ':[you, jdic['ろ'][0]],
          'ぎゃ':[dyo, jdic['か'][0]], 'ぎゅ':[dyo, jdic['く'][0]], 'ぎょ':[dyo, jdic['こ'][0]],
          'じゃ':[dyo, jdic['さ'][0]], 'じゅ':[dyo, jdic['す'][0]], 'じょ':[dyo, jdic['そ'][0]],
          'ぢゃ':[dyo, jdic['た'][0]], 'ぢゅ':[dyo, jdic['つ'][0]], 'ぢょ':[dyo, jdic['と'][0]],
          'ぴゃ':[hyo, jdic['は'][0]], 'びゅ':[hyo, jdic['ふ'][0]], 'びょ':[hyo, jdic['ほ'][0]],
          'びゃ':[dyo, jdic['は'][0]], 'ぴゅ':[dyo, jdic['ふ'][0]], 'ぴょ':[dyo, jdic['ほ'][0]],
          'いぇ':[you, jdic['え'][0]],
          'しぇ':[you, jdic['せ'][0]],
          'じぇ':[dyo, jdic['せ'][0]],
          'てぃ':[you, jdic['ち'][0]],
          'ちぇ':[you, jdic['て'][0]],
          'でぃ':[dyo, jdic['ち'][0]],
          'てゅ':[hyo, jdic['つ'][0]],
          'でゅ':[hyo+dak, jdic['つ'][0]],
          'うぃ':[[2,6], jdic['い'][0]],'うぇ':[[2,6], jdic['え'][0]],'うぉ':[[2,6], jdic['お'][0]],
          'くぁ':[[2,6],[1,6]],
          'ぐぁ':[[2,6]+dak,[1,6]],
          'つぁ':[[2,6],jdic['あ'][0]+[3,5]],
          'つぃ':[[2,6],jdic['い'][0]+[3,5]],
          'つぇ':[[2,6],jdic['え'][0]+[3,5]],
          'つぉ':[[2,6],jdic['お'][0]+[3,5]],
          'ふぁ':[[2,6],jdic['あ'][0]+[3,6]],
          'ふぃ':[[2,6],jdic['い'][0]+[3,6]],
          'ふぇ':[[2,6],jdic['え'][0]+[3,6]],
          'ふぉ':[[2,6],jdic['お'][0]+[3,6]],
          'ゔぁ':[[2,6]+dak,jdic['あ'][0]+[3,6]],
          'ゔぃ':[[2,6]+dak,jdic['い'][0]+[3,6]],
          'ゔぅ':[[2,6]+dak,jdic['う'][0]+[3,6]],
          'ゔぇ':[[2,6]+dak,jdic['え'][0]+[3,6]],
          'ゔぉ':[[2,6]+dak,jdic['お'][0]+[3,6]]
        }

def gen_cone (x, y, r1, r2, h):
    doc.addObject("Part::Cone", "Cone")
    doc.ActiveObject.Radius1 = f'{r1} mm'
    doc.ActiveObject.Radius2 = f'{r2} mm'
    doc.ActiveObject.Height = f'{h} mm'
    doc.ActiveObject.Placement = App.Placement(App.Vector(x,y,0),App.Rotation(App.Vector(0,0,1),0))
    doc.recompute()

def gen_base(x, y, z, l, w, h):
    doc.addObject("Part::Box", "Box")
    doc.ActiveObject.Placement = App.Placement(App.Vector(x, y,z),App.Rotation(App.Vector(0,0,1),0))
    doc.ActiveObject.Length = f'{l} mm'
    doc.ActiveObject.Width = f'{w} mm'
    doc.ActiveObject.Height = f'{h} mm'
    doc.recompute()


text =   PySide.QtGui.QInputDialog.getText(None, "点字生成", "点字にする文字列（ひらがな）")[0]
print(text)

text = re.sub("([0-9]+)",  '数' '\\1',text) # 数字連鶴の頭に「数」を付加
text = re.sub("([a-zA-Z]+)",  '外' '\\1',text) # 英字連続の頭に「外」を付加
text = re.sub("([^A-Z])([A-Z])([^A-Z])",  '\\1' '大' '\\2' '\\3',text) # 英大文字が１つの場合
text = re.sub("([^A-Z]*)([A-Z]{2,})([^A-Z]*)",  '\\1' '拡' '\\2' ' \\3',text) # 英大文字が２つ以上連続する場合
text = re.sub("([A-Z])([あ-ん])",  '\\1' '継' '\\2',text) # 英字の後に平仮名が続く場合
text = re.sub("([0-9])([あ-ん])",  '\\1' '継' '\\2',text) # 数字の後に平仮名が続く場合
print(text)

#
# 拗音などに対応する前処理（"あぎゃいぎゅしょ" -> ['あ', 'ぎゃ', 'い', 'ぎゅ', 'しょ']）
# 
prop = [2 if c == 'ゃ' or c=='ゅ' or c == 'ょ' or c=='ぁ' or c=='ぃ' or c=='ぅ' or c=='ぉ' or c=='ぇ' else 1 for c in text ]
prop.reverse()
out = []
flag = False
for x in prop:
    if x == 2:
        flag = True
        out.append(x)
    elif not flag:
        out.append(x)
    elif flag:
        flag = False
out.reverse()
prop = out

out = []
for i in prop:
    if i == 1:
        out.append(text[0])
        text = text[1:]
    else:
        out.append(text[0]+text[1])
        text = text[2:]
text = out
#
# 点字モデリング
#
wx = 2.13      # 点間（横）
wy = 2.37      # 点間（縦）
wc = 3.27      # マス間
gyokan = 9.17  # 行間
fringe_y = gyokan / 2.0
r1 = 1.5 /2.0  # 点の半径（底）
r2 = 1.0 /2.0  # 点の半径（TOP）
h = 0.5        # 点の高さ

links = []  # Compound に統合するためのリンク

i = 0
for ch in text:
    if len(ch) == 1:
        data = jdic[ch]
    if len(ch) == 2:
        data = jdic2[ch]
    for datum in data:
        i += 1
        for dotnum in datum:
            x = (dotnum -1) // 3
            y = (dotnum +2) % 3
            x = x * wx
            y = y * wy
            gen_cone(x + (wx + wc)*i , -y, r1, r2, h)
            links.append(doc.getObject(doc.ActiveObject.Name))
        gen_base(-wc/2.0 +(wx +wc)*i, -wy*2 -fringe_y, -h, wx + wc, (wy + fringe_y)*2, h)
        links.append(doc.getObject(doc.ActiveObject.Name))

doc.recompute()
doc.addObject("Part::Compound","Compound")
doc.ActiveObject.Links = links
doc.recompute()
Gui.activeDocument().activeView().viewIsometric()
Gui.SendMsgToActiveView("ViewFit")
